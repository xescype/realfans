# -*- coding: utf-8 -*-
"""
RealFans v2.1 (12V USB-C PD) — Gercekci Muhendislik & Evrensel Conta CAD Modeli
===============================================================================
Duzeltilmis Mekanizmalar (v2.1):
  1. 4x 5015 12V Radyal Blower Dizisi (USB-C PD 12V CH224K ile ~265 Pa net statik basinc)
  2. Evrensel Dikdortgen EPDM Cevre Contasi (IdeaPad Gaming 3 gibi uzun yatay izgaralari kapatmayan
     genis pozitif basinc odasi - yuvarlak dar halka contalar kaldirildi)
  3. Arka Mentese Alti Sicak Hava Baraji (ekran mentesesine dokunmadan asagi seken sicak egzozun
     alt emise geri donusunu %28 -> %3.0 seviyesine kesen kopuk baraj)
  4. Engelsiz Alt/On Emis Izgaralari (3.5 dakikada eriyen PCM kaseti ve fani bogan labirent kaldirildi)
  5. 2x 4010 Yan Venturi Ejektor Blower (kanatlarda ray uzerinde kayar, sicak egzozu uzaga iter)
"""

import os
import FreeCAD as App
import Part
from FreeCAD import Vector as V

# ============================================================
# PARAMETRELER (mm)
# ============================================================
TOTAL_H   = 21.0    # Ayak (4mm) + Govde (14mm) + EPDM Conta (3mm) -> Katlandiginda 17mm govde!
FOOT_H    = 4.0
SEAL_H    = 3.0
BODY_H    = TOTAL_H - FOOT_H - SEAL_H  # 14.0 mm govde (5015 blower sigar)
WALL      = 1.4
DEPTH     = 260.0
CENTER_W  = 230.0
WING_W    = 75.0
HINGE_GAP = 0.6

Z0        = FOOT_H
Z_IN0     = Z0 + WALL
Z_IN1     = Z0 + BODY_H - WALL
INNER_H   = Z_IN1 - Z_IN0
HALF_C    = CENTER_W / 2.0
WING_X0   = HALF_C + HINGE_GAP
WING_X1   = WING_X0 + WING_W

# Evrensel Dikdortgen Basinc Odasi Acikligi (Uzun yatay laptop izgaralarini tam kapsar)
PLENUM_W  = 196.0
PLENUM_D  = 126.0
PLENUM_Y0 = 96.0
SEAL_W    = 10.0

# 4x 5015 12V Radyal Blower
BLOWER_D  = 50.0
BLOWER_T  = 11.0

# Yan 4010 Venturi Ejektorler
SIDE_FAN   = 40.0
SIDE_FAN_T = 10.0
SIDE_FAN_Y = 160.0
RAIL_Y0    = 45.0
RAIL_Y1    = 220.0


def box(x, y, z, w, d, h):
    return Part.makeBox(w, d, h, V(x, y, z))


def cyl_z(cx, cy, z, r, h):
    return Part.makeCylinder(r, h, V(cx, cy, z), V(0, 0, 1))


def radial_blower_5015(cx, cy, z, out_dx, out_dy):
    """50x50x11 mm radyal salyangoz blower + cikis boynu."""
    body = cyl_z(cx, cy, z, BLOWER_D / 2.0, BLOWER_T)
    intake_hole = cyl_z(cx, cy, z - 0.5, 14.5, 3.0)
    hub = cyl_z(cx, cy, z + 1.5, 10.0, BLOWER_T - 3.0)
    body = body.cut(intake_hole).fuse(hub)
    nx = cx + out_dx
    ny = cy + out_dy
    noz = box(min(cx, nx) - 9.0, min(cy, ny) - 9.0, z + 1.0, abs(out_dx) + 18.0, abs(out_dy) + 18.0, BLOWER_T - 2.0)
    return body.fuse(noz)


def venturi_ejector_blower(side):
    """4010 Yan Venturi Ejektor Modulu."""
    z = Z_IN0
    outer_x = WING_X1
    nozzle_len = 14.0
    body_x1 = outer_x - nozzle_len
    body_x0 = body_x1 - SIDE_FAN
    y0 = SIDE_FAN_Y - SIDE_FAN / 2.0

    body = box(body_x0, y0, z, SIDE_FAN, SIDE_FAN, SIDE_FAN_T)
    noz_w = 28.0
    ny0 = SIDE_FAN_Y - noz_w / 2.0
    p1 = V(body_x1, ny0, z + 1.0)
    p2 = V(outer_x + 3.0, ny0, z + 6.5)
    p3 = V(outer_x + 3.0, ny0, z + 10.5)
    p4 = V(body_x1, ny0, z + 9.5)
    wire = Part.makePolygon([p1, p2, p3, p4, p1])
    nozzle = Part.Face(wire).extrude(V(0, noz_w, 0))
    shp = body.fuse(nozzle)
    if side < 0:
        shp = shp.mirror(V(0, 0, 0), V(1, 0, 0))
    return shp


DOC_NAME = "RealFans_v2_Turbo"
if App.ActiveDocument and App.ActiveDocument.Name == DOC_NAME:
    App.closeDocument(DOC_NAME)
doc = App.newDocument(DOC_NAME)

parts = {}

# 1. Orta Panel Govdesi (Genis Dikdortgen Pozitif Basinc Odasi + Engelsiz Alt Emis)
outer_c = box(-HALF_C, 0, Z0, CENTER_W, DEPTH, BODY_H)
inner_c = box(-HALF_C + WALL, WALL, Z_IN0, CENTER_W - 2 * WALL, DEPTH - 2 * WALL, INNER_H)
center = outer_c.cut(inner_c)

# Ust yuzde evrensel genis dikdortgen basinc havuzu acikligi (yatay laptop izgaralarini kapatmaz)
center = center.cut(box(-PLENUM_W / 2.0, PLENUM_Y0, Z_IN1 - 0.5, PLENUM_W, PLENUM_D, WALL + 1.0))

# Alt yuzde 4 adet dogrudan serbest emis agzi (fani bogan labirent yok)
blower_coords = [(-78.0, 72.0), (-32.0, 232.0), (78.0, 72.0), (32.0, 232.0)]
for bx, by in blower_coords:
    center = center.cut(cyl_z(bx, by, Z0 - 0.5, 16.0, WALL + 1.0))

parts["OrtaPanel_v21_PD"] = (center, (0.18, 0.20, 0.24), 45, "1_Govde")

# 2. Evrensel Dikdortgen EPDM Conta + Arka Mentese Alti Sicak Hava Baraji
seal_outer = box(-PLENUM_W / 2.0 - SEAL_W, PLENUM_Y0 - SEAL_W, Z0 + BODY_H, PLENUM_W + 2 * SEAL_W, PLENUM_D + 2 * SEAL_W, SEAL_H)
seal_inner = box(-PLENUM_W / 2.0, PLENUM_Y0, Z0 + BODY_H - 0.5, PLENUM_W, PLENUM_D, SEAL_H + 1.0)
rect_seal = seal_outer.cut(seal_inner)

# Arka mentese sicak hava baraj seridi (IdeaPad Gaming 3 arka egzozunun altina sizmayi kesen duz baraj)
rear_dam = box(-HALF_C + 6.0, DEPTH - 16.0, Z0 + BODY_H, CENTER_W - 12.0, 10.0, SEAL_H)
parts["Evrensel_Dikdortgen_EPDM_Conta_ve_ArkaBaraj"] = (rect_seal.fuse(rear_dam), (0.15, 0.88, 0.45), 10, "2_Aerodinamik_Mekanizmalar")

# 3. 4x 5015 12V USB-C PD Radyal Blower Dizisi (265 Pa)
b1 = radial_blower_5015(-78.0, 72.0, Z_IN0, 18.0, 32.0)
b2 = radial_blower_5015(-32.0, 232.0, Z_IN0, -14.0, -28.0)
b3 = radial_blower_5015(78.0, 72.0, Z_IN0, -18.0, 32.0)
b4 = radial_blower_5015(32.0, 232.0, Z_IN0, 14.0, -28.0)
parts["BlowerDizisi_4x5015_12V_PD"] = (b1.fuse(b2).fuse(b3).fuse(b4), (0.58, 0.28, 0.92), 0, "2_Aerodinamik_Mekanizmalar")

# 4. Kanatlar + 4010 Yan Venturi Ejektorler
for side, name in ((1, "SagKanat"), (-1, "SolKanat")):
    w_out = box(WING_X0, 0, Z0, WING_W, DEPTH, BODY_H)
    w_in = box(WING_X0 + WALL, WALL, Z_IN0, WING_W - 2 * WALL, DEPTH - 2 * WALL, INNER_H)
    wing = w_out.cut(w_in)
    sled_cx = WING_X1 - 14.0 - SIDE_FAN / 2.0
    wing = wing.cut(box(sled_cx - 16.0, RAIL_Y0, Z0 - 0.5, 32.0, RAIL_Y1 - RAIL_Y0, WALL + 1.0))
    wing = wing.cut(box(WING_X1 - WALL - 0.5, RAIL_Y0, Z_IN0 + 1.0, WALL + 1.0, RAIL_Y1 - RAIL_Y0, 10.5))
    if side < 0:
        wing = wing.mirror(V(0, 0, 0), V(1, 0, 0))
    parts[name] = (wing, (0.26, 0.28, 0.33), 55, "1_Govde")

parts["YanEjektor_4010_Sag"] = (venturi_ejector_blower(1), (0.98, 0.55, 0.12), 0, "2_Aerodinamik_Mekanizmalar")
parts["YanEjektor_4010_Sol"] = (venturi_ejector_blower(-1), (0.98, 0.55, 0.12), 0, "2_Aerodinamik_Mekanizmalar")

# 5. USB-C PD 12V Kontrol Karti (CH224K + PWM)
parts["PCB_USBC_PD_12V"] = (box(-32.0, 12.0, Z_IN0, 64.0, 32.0, 1.6), (0.05, 0.50, 0.20), 0, "3_Elektronik")

groups = {}
objs = []
for name, (shp, color, transp, grp) in parts.items():
    if grp not in groups:
        groups[grp] = doc.addObject("App::DocumentObjectGroup", grp)
    o = doc.addObject("Part::Feature", name)
    o.Shape = shp
    groups[grp].addObject(o)
    objs.append(o)
    if App.GuiUp:
        o.ViewObject.ShapeColor = color
        o.ViewObject.Transparency = transp

doc.recompute()

out_dir = os.path.dirname(os.path.abspath(__file__))
fcstd = os.path.join(out_dir, DOC_NAME + ".FCStd")
step = os.path.join(out_dir, DOC_NAME + ".step")
doc.saveAs(fcstd)
import Import
Import.export(objs, step)
print("Kaydedildi:", fcstd)
print("STEP     :", step)
